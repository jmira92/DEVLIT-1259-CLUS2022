module esc_types {
 /*
  * This file contains custom data types that are used by all other YANG models.
  */
  namespace "http://www.cisco.com/esc/esc_types";
  prefix "types";

  import ietf-inet-types { prefix "ietf-inet-types"; }
  import ietf-yang-types { prefix "ietf-yang-types"; }

  organization "Cisco Systems";

  contact "Shesha Sreenivasamurthy <shesha@cisco.com>";

  description
    "ESC's types declarations";

  revision 2014-06-23 {
    description "ESC Types";
  }

  /****************** ESC DATA TYPES **********************/
  /*
   * Generic esc data type where you can specify xpath or actual value
   */
  typedef escxpath { type string { pattern "xpath:.+"; } }
  typedef escempty { type string { pattern ""; } } /* Currently unused */

  typedef escfloat {
    type string;
    reference "http://www.w3.org/TR/xmlschema-2/#float";
  }

  typedef escint8 {
    type union {
      type int8;
      type escxpath;
    }
  }
  typedef escint16 {
    type union {
      type int16;
      type escxpath;
    }
  }
  typedef escint32 {
    type union {
      type int32;
      type escxpath;
    }
  }
  typedef escbool {
    type union {
      type boolean;
      type escxpath;
    }
  }
  typedef escipaddr {
    type union {
      type ietf-inet-types:ip-address;
      type escxpath;
    }
  }
  typedef escmacaddr {
    type union {
      type ietf-yang-types:mac-address;
      type escxpath;
    }
  }
  typedef escuri {
    type union {
      type ietf-inet-types:uri;
      type escxpath;
    }
  }
  typedef escname {
    type union {
      type string { length 1..256; }
      type escxpath;
    }
  }
  typedef escversion {
    type union {
      type string { length 1..16; }
      type escxpath;
    }
  }
  typedef escdescription {
    type union {
      type string { length 1..8192; }
      type escxpath;
    }
  }
  typedef escnetname {
    type union {
      /*
       * Network name. 1024 is the max length allowed by
       * underlying infrastructure.
       */
      type string { length 1..1024; }
      type escxpath;
    }
  }
  typedef escfilepath {
    type union {
      type string { length 1..1024; }
      type escxpath;
    }
  }
  typedef escbigdata {
    type union {
      type string { length 1..16384; } /* 16K */
      type escxpath;
    }
  }
  typedef escratio {
    type union {
      type string { pattern "[0-9]+:[0-9]+"; }
      type escxpath;
    }
  }
  typedef escvlanid {
    type union {
      type int16 {
        range "0..4094";
      }
      type escxpath;
    }
  }

  typedef license_key_type {
    type union {
        type enumeration {
            enum mac_addr;
        }

        type types:escxpath;
    }
  }

  typedef license_key_value {
    type string { length 1..256; }
  }
  /****************** EVENT TYPES **********************/
  /*
   * These are the event types that are defined in EDCS: 1312696.
   * This represents the events/callbacks generated by Core-ESC.
   */
  typedef event_types {
    type enumeration {
      enum CREATE_NETWORK;
      enum DELETE_NETWORK;
      enum CREATE_SUBNET;
      enum DELETE_SUBNET;
      enum CREATE_TENANT;
      enum DELETE_TENANT;
      enum SERVICE_REGISTRATION;
      enum SERVICE_UNREGISTRATION;
      enum VM_DEPLOYED;
      enum VM_ALIVE;
      enum VM_UNDEPLOYED;
      enum SERVICE_ALIVE;
      enum SERVICE_UNDEPLOYED;
      enum VM_SCALE_OUT_INIT;
      enum VM_SCALE_OUT_DEPLOYED;
      enum VM_SCALE_OUT_COMPLETE;
      enum VM_SCALE_IN_INIT;
      enum VM_SCALE_IN_COMPLETE;
      enum VM_RECOVERY_INIT;
      enum VM_RECOVERY_DEPLOYED;
      enum VM_RECOVERY_UNDEPLOYED;
      enum VM_RECOVERY_COMPLETE;
      enum SERVICE_UPDATED;
      enum VM_STOPPED;
      enum SERVICE_STOPPED;
      enum VM_STARTED;
      enum VM_REBOOTED;
      enum VM_MONITOR_UNSET;
      enum SERVICE_MONITOR_UNSET;
      enum VM_MONITOR_SET;
      enum ESC_IN_SERVICE;
      enum ESC_OUT_OF_SERVICE;
    }
  }

  /****************** STATUS **********************/
  /*
   * These represent status of the operation requested that
   * are notified to northbound client.
   */

  typedef status {
    type enumeration {
      enum SUCCESS;
      enum FAILURE;
    }
  }

  /****************** SIZE UNITS  **********************/
  /*
   * This is derived from the generic sizeunit_group defined below.
   * Standard size units.
   */
  typedef szunits {
    description "Some standard size units: MiB, GiB, TiB, PiB and EiB.
                        MiB: 1024^2 (Mebibyte)
                        GiB: 1024^3 (Gibibyte)
                        TiB: 1024^4 (Tebibyte)
                        PiB: 1024^5 (Pebibyte)
                        EiB: 1024^6 (Exbibyte)";
    type union {
      type enumeration {
        enum MiB;
        enum GiB;
        enum TiB;
        enum PiB;
        enum EiB;
      }
      type escxpath;
    }
  }

  /****************** IOBUS TYPE  **********************/
  /*
   * Standard IO bus used to attach root/OS disk and secondary volume.
   */
  typedef iobus {
    description "PCI bus interface that is to be used while attaching the OS
                 disk to the domain. Currently supported bus types are IDE,
                 SCSI and VIRTIO";
    type union {
      type enumeration {
        enum ide;
        enum scsi;
        enum virtio;
      }
      type escxpath;
    }
  }

  /****************** INTERFACE TYPE  **********************/
  typedef iface_type {
    description "Interface Type: VIRTUAL/PASSTHRU";
    type union {
      type enumeration {
        enum virtual;
        enum passthru;
      }
      type escxpath;
    }
  }

  /****************** VIRTUAL INTERFACE MODEL  **********************/
  /*
   * Types of virtual intreface models
   */
  typedef iface_model {
    description
      "Virtual Interface Type: virtio/e1000. Later when we support
       'passthru' interface type we can change this to a union";
    type union {
      type enumeration {
        enum virtio;
        enum e1000;
      }
      type types:escxpath;
    }
  }

  /****************** IP VERSIONS **********************/
  typedef ipversion_t {
    description "ipv4 or ipv6";
    type union {
      type enumeration {
        enum ipv4;
        enum ipv6;
      }
      type types:escxpath;
    }
  }

  /****************** DISK FORMATS **********************/
  /*
   * Rather than specifying disk formats as a string where user may
   * get confused with what to specify, here having it like an enumeration
   * that enables the user to know what are the different options that are
   * available for him/her.
   */
  typedef disk_formats {
    description "The format of the disk that is being specified as disk source.
                 Currently QCOW2, RAW and VMDK formats are supported.";
    type enumeration {
      enum qcow2;
      enum raw;
      enum vmdk;
    }
  }


  /*******************   METRIC CONDITIONS *****************/
  typedef conditions {
    description
      "Different conditions supported with respect to metric comparison";
    type union {
      type enumeration {
        enum GT;
        enum LT;
        enum EQ;
        enum GE;
        enum LE;
      }
      type types:escxpath;
    }
  }

  /*********************   METRIC TYPES ********************/
  typedef metric_types {
    description
      "Different conditions supported with respect to metric comparison";
    type union {
      type enumeration {
        enum INT8;
        enum INT16;
        enum INT32;
        enum UINT8;
        enum UINT16;
        enum UINT32;
        enum FLOAT;
        enum DOUBLE;
        enum STRING;
      }
      type types:escxpath;
    }
  }

  /*******************  METRIC POLLING UNITS *****************/
  typedef pollunits {
    description "Polling units, seconds or minutes";
    type union {
      type enumeration {
        enum minutes;
        enum seconds;
      }
      type types:escxpath;
    }
  }

  /************ WATCH DOG HARDWARE ************/
  typedef wd_hardware {
    description "Only certain Watchdog hardware are supported current.";
    type enumeration {
      enum i6300esb;
      enum ib700;
    }
  }

  /************ WATCH DOG ACTION ************/
  typedef wd_action {
    description
      "Action that should be taken by the hypervisor when watchdog
       is triggered";
    type enumeration {
      enum reset;
      enum poweroff;
      enum shutdown;
      enum pasue;
      enum debug;
      enum none;
    }
  }

  /************ PLACEMENT AFFINITY TYPES ************/
  typedef placement_type {
    description
      "Whether VMs of two groups to be place together (affinity) or on separate
       hosts (anti_affinity)";
    type union {
      type enumeration {
        enum affinity;
        enum anti_affinity;
      }
      type types:escxpath;
    }
  }

  /************ PLACEMENT ENFORCEMENT TYPES ************/
  typedef enforcement {
    description
      "Whether the affinity policy should be strictly or loosely enforced";
    type union {
      type enumeration {
        enum strict;
        /* CSCus83505comment out loose since it is not supported at this time -
           when availability zone/aggregates are properly supported, loose
           should be returned as a valid option, so comment out rather than
           remove enum loose;
        */
      }
      type types:escxpath;
    }
  }

  /****** SERVICE STATE MACHINE STATES *********/
  typedef service_state_machine_states {
    description "Service state machines states";
    type enumeration {
      enum SERVICE_UNDEF_STATE;
      enum SERVICE_DEPLOYING_STATE;
      enum SERVICE_INERT_STATE;
      enum SERVICE_ACTIVE_STATE;
      enum SERVICE_UNDEPLOYING_STATE;
      enum SERVICE_STOPPING_STATE;
      enum SERVICE_STOPPED_STATE;
      enum SERVICE_STARTING_STATE;
      enum SERVICE_REBOOTING_STATE;
      enum SERVICE_ERROR_STATE;
    }
  }

  /****** VM STATE MACHINE STATES *********/
  typedef vm_state_machine_states {
    description "VM state machines states";
    type enumeration {
      enum VM_UNDEF_STATE;
      enum VM_DEPLOYING_STATE;
      enum VM_MONITOR_UNSET_STATE;
      enum VM_MONITOR_DISABLED_STATE;
      enum VM_STOPPING_STATE;
      enum VM_SHUTOFF_STATE;
      enum VM_STARTING_STATE;
      enum VM_REBOOTING_STATE;
      enum VM_INERT_STATE;
      enum VM_ALIVE_STATE;
      enum VM_UNDEPLOYING_STATE;
      enum VM_ERROR_STATE;
    }
  }

    /****** VM GROUP PROPERTIES *********/
  typedef vm_group_properties {
    description "vm_group_properties";
    type enumeration {
      enum NOTIFY_EXTERNAL_MONITOR;
    }
  }

  /****** SERVICE/VM OPERATION TYPES *********/
  typedef action_types {
    description "Service/VM action types";
    type enumeration {
      enum STOP;
      enum START;
      enum REBOOT;
      enum DISABLE_MONITOR;
      enum ENABLE_MONITOR;
    }
  }
}
