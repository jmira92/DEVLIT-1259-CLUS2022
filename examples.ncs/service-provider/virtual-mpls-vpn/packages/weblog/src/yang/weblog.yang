module weblog {

  namespace "http://com/example/weblog";
  prefix weblog;

  import ietf-inet-types {
    prefix inet;
  }

  import tailf-common {
    prefix tailf;
  }

  import tailf-ncs {
    prefix ncs;
  }

  container logs {
    list web {
      config false;
      tailf:cdb-oper;
      key timestamp;

      leaf timestamp {
        description "Number of milliseconds since Jan 1, 1970, 00:00:00 GMT";
        type uint64;
      }

      leaf timestamp_text {
        type string;
      }

      leaf message {
        type string;
      }
    }
  } // logs
}
