module syslog-service {

  namespace "http://example.com/syslog-service";
  prefix sls;

  import ietf-inet-types {
    prefix inet;
  }

  import tailf-common {
    prefix tailf;
  }

  import tailf-ncs {
    prefix ncs;
  }


  description
    "This service ensures that we have the same syslog settings
     on all routers in our network. ";

  revision 2012-07-08 {
    description
      "Initial revision.";
  }

  typedef syslogLevel {
    type enumeration {
      enum "emerg";
      enum "alert";
      enum "crit";
      enum "err";
      enum "warning";
      enum "notice";
      enum "info";
      enum "debug";
      enum "none";
      enum "all";
    }
  }

  typedef syslogFacility {
    type enumeration {
      enum "auth";
      enum "authpriv";
      enum "cron";
      enum "daemon";
      enum "ftp";
      enum "kern";
      enum "lpr";
      enum "mail";
      enum "news";
      enum "security";
      enum "syslog";
      enum "user";
      enum "uucp";
      enum "local0";
      enum "local1";
      enum "local2";
      enum "local3";
      enum "local4";
      enum "local5";
      enum "local6";
      enum "local7";
      enum "all";
    }
  }

  augment /ncs:services {
    container syslog {
      presence "Singelton Syslog service";

      uses ncs:service-data;
      ncs:servicepoint syslog-servicepoint;

      leaf-list devices {
        type leafref {
          path "/ncs:devices/ncs:device/ncs:name";
        }
      }

      list server {
        key "name";
        leaf name {
          type inet:host;
        }
        leaf enabled {
          type boolean;
        }
        list selector {
          key "name";
          leaf name {
            type int32;
          }
          leaf negate {
            type boolean;
          }
          leaf comparison {
            type enumeration {
              enum "same-or-higher";
              enum "same";
            }
          }
          leaf level {
            type syslogLevel;
          }
          leaf-list facility {
            type syslogFacility;
            min-elements 1;
            max-elements "8";
          }
        }
      }
    }
  }
}
