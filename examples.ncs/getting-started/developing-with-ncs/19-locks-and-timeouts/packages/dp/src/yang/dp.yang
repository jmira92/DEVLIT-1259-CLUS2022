module dp {

  namespace "http://com/example/dp";
  prefix dp;

  import tailf-common {
    prefix tailf;
  }


  // This is a skeleton for a simple made up data provider,
  // the package has been generated by ncs-make-package

  container test-stats {
    config false;
    tailf:callpoint "test-stats-cp";
    list item {
      key name;
      leaf name {
        type string;
      }
      leaf i {
        type int32;
      }
    }
  }
}
