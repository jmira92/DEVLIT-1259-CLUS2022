module SNMP-USER-BASED-SM-MIB-ncs-ann {
  namespace "urn:dummy-ncs";
  prefix dummy-ncs;

  import tailf-common {
    prefix tailf;
  }
  import SNMP-USER-BASED-SM-MIB {
    prefix x;
  }

  tailf:annotate "/x:SNMP-USER-BASED-SM-MIB/x:usmUserTable/x:usmUserEntry" {
    must "usmUserAuthProtocol != '1.3.6.1.6.3.10.1.1.2'" {
      error-message "The MD5 authentication protocol is not allowed.";
    }
    must "usmUserPrivProtocol != '1.3.6.1.6.3.10.1.2.2'" {
      error-message "The DES privacy protocol is not allowed.";
    }
  }
}
