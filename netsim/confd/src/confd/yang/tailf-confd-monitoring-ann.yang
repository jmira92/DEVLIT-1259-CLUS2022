module tailf-confd-monitoring-ann {
  namespace "urn:dummy";
  prefix dummy;

  import tailf-common {
    prefix tailf;
  }
  import tailf-confd-monitoring {
    prefix tfcm;
  }

  description
    "Copyright 2019 Cisco Systems, Inc.
     All rights reserved.
     Permission is hereby granted to redistribute this file without
     modification.";


  tailf:annotate "/tfcm:confd-state" {
    tailf:callpoint "confd" {
      tailf:internal;
    }

    tailf:info "Display ConfD status information";
  }
}
