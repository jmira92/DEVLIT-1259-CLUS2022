module tailf-restconf {
  namespace "http://tail-f.com/ns/tailf-restconf";
  prefix "tfrcr";

  tailf:export none;

  import tailf-common {
    prefix tailf;
  }
  import ietf-restconf {
    prefix rc;
  }
  import tailf-rollback {
    prefix rollback;
  }

  description
    "Copyright 2020 Cisco Systems, Inc.
     All rights reserved.
     Permission is hereby granted to redistribute this file without
     modification.";

  revision 2020-06-25 {
    description
      "Initial revision, released as part of ConfD-7.4 / NCS-5.4.";
  }

  tailf:structure result {
    container result {
      uses rollback:rollback-commit-result;
    }
  }
}
