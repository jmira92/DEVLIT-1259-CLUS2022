submodule snmp-usm {

  belongs-to snmp {
    prefix snmp;
  }

  import ietf-yang-types {
    prefix yang;
  }
  import tailf-common {
    prefix tailf;
  }

  include snmp-common;

  grouping key {
    choice key-type {
      leaf password {
        /* This must be stored in the config; it cannot be derived from
           the SNMP table.  Also, if SNMP is used to set the key,
           this password will not be used anymore */
        type string;
        description
          "Will be used to create a localized key.";
      }
      leaf key {
        type yang:hex-string;
        description "Authentication key";
      }
    }
  }

  grouping user-list {
    list user {
      key "name";

      reference "SNMP-USER-BASED-SM-MIB.usmUserTable";

      leaf name {
        type snmp:identifier;
        reference "SNMP-USER-BASED-SM-MIB.usmUserName
                   SNMP-USER-BASED-SM-MIB.usmUserSecurityName";
      }
      leaf security-name {
        type snmp:identifier;
        description
          "If not set, the value of 'name' is operationally used";
        reference "SNMP-USER-BASED-SM-MIB.usmUserSecurityName";
      }
      container auth {
        presence "enables authentication";
        description "Enables authentication protocol of the user";
        choice protocol {
          mandatory true;
          reference "SNMP-USER-BASED-SM-MIB.usmUserAuthProtocol";
          container sha {
            presence "sha";
            uses key;
          }
        }
      }
      container priv {
        presence "enables encryption";
        description "Enables encryption for the authentication process";
        must "../auth" {
          error-message "when privacy is used, authentication must also be used";
          tailf:dependency "../auth";
        }
        choice protocol {
          mandatory true;
          reference "SNMP-USER-BASED-SM-MIB.usmUserPrivProtocol";
          container aes {
            presence "aes";
            uses key;
          }
        }
      }
    }
  }

  augment /snmp:snmp {

    container usm {
      description
        "Configuration of the User-based Security Model";
      container local {
        uses user-list;
      }

      list remote {
        key "engine-id";

        leaf engine-id {
          type snmp:engine-id;
          description
            "The value of this field MUST NOT be the same as the local
             engine-id, as defined by /snmp/agent/engine-id";
          reference "SNMP-USER-BASED-SM-MIB.usmUserEngineID";
        }

        uses user-list;
      }
    }
  }
}
