submodule snmp-target-params {

  belongs-to snmp {
    prefix snmp;
  }

  include snmp-common;
  include snmp-community;
  include snmp-target;
  include snmp-usm;

  reference "RFC3413: Simple Network Management Protocol (SNMP) Applications
            SNMP-TARGET-MIB";

  augment /snmp:snmp/snmp:target {

    /* By including the params directly in the target entry we
       lose some flexibility, but we get a simpler model with less
       cross-references.  In SNMP, two addrEntries can point to the same
       paramsEntry.
    */
    choice params {
      mandatory true;
      reference "SNMP-TARGET-MIB.snmpTargetParamsTable";
      container v1 {
        description "SNMPv1 parameters type";
        // mp-model is v1, sec-level is noAuthNoPriv
        leaf sec-name {
          type leafref {
            path "/snmp/community/sec-name";
          }
          mandatory true;
          reference "SNMP-TARGET-MIB.snmpTargetParamsSecurityName";
        }
      }
      container v2c {
        description "SNMPv2 community parameters type";
        // mp-model is v2c, sec-level is noAuthNoPriv
        leaf sec-name {
          type leafref {
            path "/snmp/community/sec-name";
          }
          mandatory true;
          reference "SNMP-TARGET-MIB.snmpTargetParamsSecurityName";
        }
      }
      container usm {
        description "user based SNMPv3 parameters type";
        // mp-model is v3
        leaf user-name {
          type snmp:identifier;
          mandatory true;
          reference "SNMP-TARGET-MIB.snmpTargetParamsSecurityName";
        }
        leaf sec-level {
          type sec-level;
          mandatory true;
          reference "SNMP-TARGET-MIB.snmpTargetParamsSecurityLevel";
        }
      }
    }
  }

}
