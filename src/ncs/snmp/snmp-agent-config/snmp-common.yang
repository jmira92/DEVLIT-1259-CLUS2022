submodule snmp-common {

  belongs-to snmp {
    prefix snmp;
  }

  import tailf-common {
    prefix tailf;
  }

  description
   "This submodule contains a collection of common YANG definitions
    for configuring SNMP engines via NETCONF.";

  /* Collection of SNMP features */

  feature proxy {
    description
    "A server implements this feature if it can act as an SNMP Proxy";
  }

  feature multiple-contexts {
    description
     "A server implements this feature if it supports other contexts than
     the default context.";
  }

  feature notification-filter {
    description
     "A server implements this feature if it supports SNMP notification
     filtering.";
  }

  /* Collection of SNMP specific data types */

  typedef admin-string {
    type string {
      length "0..255";
    }
    description
     "Represents an SnmpAdminString as defined in RFC 3411.";
    reference
     "RFC 3411: An Architecture for Describing SNMP Management Frameworks";
  }

  typedef identifier {
    type admin-string {
      length "1..32";
    }
    description
     "Identifiers are used to name items in the SNMP configuration
      data store.";
  }

  typedef context-name {
    type admin-string {
      length "0..32";
    }
    description
     "The context type represents an SNMP context name.";
  }

  typedef sec-name {
    type admin-string {
      length "1..32";
    }
    description
      "The sec-name type represents an SNMP security name.";
  }

  typedef mp-model {
    type union {
      type enumeration {
        enum any { value 0; }
        enum v1  { value 1; }
        enum v2c { value 2; }
        enum v3  { value 3; }
      }
      type int32 {
        range "0..2147483647";
      }
    }
    reference
     "RFC3411: An Architecture for Describing SNMP Management Frameworks";
  }

  typedef sec-model-no-wildcard {
    type union {
      type enumeration {
        enum v1  { value 1; }
        enum v2c { value 2; }
        enum usm { value 3; }
      }
      type int32 {
        range "1..2147483647";
      }
    }
    reference
     "RFC3411: An Architecture for Describing SNMP Management Frameworks";
  }

  typedef sec-model {
    type union {
      type enumeration {
        enum any { value 0; }
      }
      type sec-model-no-wildcard;
    }
    reference
     "RFC3411: An Architecture for Describing SNMP Management Frameworks";
  }

  typedef sec-level {
    type enumeration {
      enum no-auth-no-priv { value 1; }
      enum auth-no-priv    { value 2; }
      enum auth-priv       { value 3; }
    }
    reference
     "RFC3411: An Architecture for Describing SNMP Management Frameworks";
  }

  typedef engine-id {
    type tailf:hex-list {
      tailf:value-length "5..32";
    }
    reference
     "RFC3411: An Architecture for Describing SNMP Management Frameworks";
  }

  typedef wildcard-object-identifier {
    type string {
        pattern '(([0-1*](\.(([1-3]?[0-9])|[*])))|([2*]\.((0|([1-9]\d*))|[*])))'
                 + '(\.((0|([1-9]\d*))|[*]))*';
    }
    description
     "The wildcard-object-identifier type represents an SNMP object
      identifier where subidentifiers can be given either as a label,
      in numeric form, or a wildcard, represented by a *.";
  }

  container snmp {
    description
      "Top-level container for SNMP related configuration and
       status objects.";
  }

}
