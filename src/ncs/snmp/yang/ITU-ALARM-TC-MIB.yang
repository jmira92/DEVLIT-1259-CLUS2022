/*
 * Generated by confdc --mib2yang
 * Source: ITU-ALARM-TC-MIB.mib
 */
module ITU-ALARM-TC-MIB {
  namespace "http://tail-f.com/ns/mibs/ITU-ALARM-TC-MIB/200409090000Z";
  prefix ITU_ALARM_TC_MIB;
  tailf:id "";
  tailf:snmp-mib-module-name "ITU-ALARM-TC-MIB";
  import tailf-common {
    prefix tailf;
  }

  revision 2004-09-09 {
    description
      "";
  }

  typedef ItuPerceivedSeverity {
    type enumeration {
      enum "cleared" {
        value 1;
      }
      enum "indeterminate" {
        value 2;
      }
      enum "critical" {
        value 3;
      }
      enum "major" {
        value 4;
      }
      enum "minor" {
        value 5;
      }
      enum "warning" {
        value 6;
      }
    }
  }

  typedef ItuTrendIndication {
    type enumeration {
      enum "moreSevere" {
        value 1;
      }
      enum "noChange" {
        value 2;
      }
      enum "lessSevere" {
        value 3;
      }
    }
  }
}
