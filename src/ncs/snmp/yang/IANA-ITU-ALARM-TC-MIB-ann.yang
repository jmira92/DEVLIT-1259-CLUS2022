module IANA-ITU-ALARM-TC-MIB-ann {
  namespace "urn:dummy";
  prefix dummy;

  import tailf-common {
    prefix tailf;
  }

  description
    "Annotation module for the generated IANA-ITU-ALARM-TC-MIB YANG module";

  tailf:annotate-module IANA-ITU-ALARM-TC-MIB {
    tailf:annotate-statement typedef[name='IANAItuProbableCause'] {
      tailf:annotate-statement type[name='enumeration'] {
        tailf:annotate-statement enum[name='other'] {
          tailf:code-name ProbableCause_other;
        }
      }
    }
    tailf:annotate-statement typedef[name='IANAItuEventType'] {
      tailf:annotate-statement type[name='enumeration'] {
        tailf:annotate-statement enum[name='other'] {
          tailf:code-name EventType_other;
        }
      }
    }
  }
}
