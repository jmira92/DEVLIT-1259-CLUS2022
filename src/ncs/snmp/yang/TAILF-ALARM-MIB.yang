/*
 * Generated by confdc --mib2yang
 * Source: TAILF-ALARM-MIB.mib
 */
module TAILF-ALARM-MIB {
  namespace "http://tail-f.com/ns/mibs/TAILF-ALARM-MIB/201610080000Z";
  prefix TAILF_ALARM_MIB;
  tailf:id "";
  tailf:snmp-mib-module-name "TAILF-ALARM-MIB";

  import ietf-yang-types {
    prefix yang;
  }
  import tailf-common {
    prefix tailf;
  }
  import TAILF-ALARM-TC-MIB {
    prefix TAILF-ALARM-TC-MIB;
  }
  import SNMPv2-TC {
    prefix SNMPv2-TC;
  }
  import SNMP-FRAMEWORK-MIB {
    prefix SNMP-FRAMEWORK-MIB;
  }
  import ITU-ALARM-TC-MIB {
    prefix ITU-ALARM-TC-MIB;
  }
  import IANA-ITU-ALARM-TC-MIB {
    prefix IANA-ITU-ALARM-TC-MIB;
  }

  revision 2016-10-08 {
    description
      "";
  }

  container TAILF-ALARM-MIB {
    container tfAlarms {
      tailf:snmp-oid "1.3.6.1.4.1.24961.2.103.1.1";
      config false;
      leaf tfAlarmNumber {
        type uint32;
        tailf:snmp-oid "1.3.6.1.4.1.24961.2.103.1.1.1";
        config false;
      }
      leaf tfAlarmLastChanged {
        type yang:date-and-time;
        tailf:snmp-oid "1.3.6.1.4.1.24961.2.103.1.1.2";
        config false;
      }
    }
    container tfAlarmTable {
      config false;
      list tfAlarmEntry {
        key "tfAlarmIndex";
        tailf:sort-order "snmp";
        config false;
        tailf:snmp-oid "1.3.6.1.4.1.24961.2.103.1.1.5";
        leaf tfAlarmIndex {
          type TAILF-ALARM-TC-MIB:TfAlarmIndex;
          tailf:snmp-oid "1.3.6.1.4.1.24961.2.103.1.1.5.1.1";
        }
        leaf tfAlarmType {
          type SNMP-FRAMEWORK-MIB:SnmpAdminString;
          tailf:snmp-oid "1.3.6.1.4.1.24961.2.103.1.1.5.1.2";
          config false;
        }
        leaf tfAlarmDevice {
          type SNMP-FRAMEWORK-MIB:SnmpAdminString;
          tailf:snmp-oid "1.3.6.1.4.1.24961.2.103.1.1.5.1.3";
          config false;
        }
        leaf tfAlarmObject {
          type TAILF-ALARM-TC-MIB:TfYANGResource;
          tailf:snmp-oid "1.3.6.1.4.1.24961.2.103.1.1.5.1.4";
          config false;
        }
        leaf tfAlarmObjectOID {
          type yang:object-identifier;
          tailf:snmp-oid "1.3.6.1.4.1.24961.2.103.1.1.5.1.5";
          config false;
        }
        leaf tfAlarmObjectStr {
          type TAILF-ALARM-TC-MIB:TfUtf8String;
          tailf:snmp-oid "1.3.6.1.4.1.24961.2.103.1.1.5.1.6";
          config false;
        }
        leaf tfAlarmSpecificProblem {
          type TAILF-ALARM-TC-MIB:TfUtf8String;
          tailf:snmp-oid "1.3.6.1.4.1.24961.2.103.1.1.5.1.7";
          config false;
        }
        leaf tfAlarmEventType {
          type IANA-ITU-ALARM-TC-MIB:IANAItuEventType;
          tailf:snmp-oid "1.3.6.1.4.1.24961.2.103.1.1.5.1.8";
          config false;
        }
        leaf tfAlarmProbableCause {
          type TAILF-ALARM-TC-MIB:TfProbableCause;
          tailf:snmp-oid "1.3.6.1.4.1.24961.2.103.1.1.5.1.9";
          config false;
        }
        leaf tfAlarmOrigTime {
          type yang:date-and-time;
          tailf:snmp-oid "1.3.6.1.4.1.24961.2.103.1.1.5.1.10";
          config false;
        }
        leaf tfAlarmTime {
          type yang:date-and-time;
          tailf:snmp-oid "1.3.6.1.4.1.24961.2.103.1.1.5.1.11";
          config false;
        }
        leaf tfAlarmSeverity {
          type ITU-ALARM-TC-MIB:ItuPerceivedSeverity;
          tailf:snmp-oid "1.3.6.1.4.1.24961.2.103.1.1.5.1.12";
          config false;
        }
        leaf tfAlarmCleared {
          type SNMPv2-TC:TruthValue;
          tailf:snmp-oid "1.3.6.1.4.1.24961.2.103.1.1.5.1.13";
          config false;
        }
        leaf tfAlarmText {
          type TAILF-ALARM-TC-MIB:TfUtf8String;
          tailf:snmp-oid "1.3.6.1.4.1.24961.2.103.1.1.5.1.14";
          config false;
        }
        leaf tfAlarmOperatorState {
          type TAILF-ALARM-TC-MIB:TfAlarmOperatorState;
          tailf:snmp-oid "1.3.6.1.4.1.24961.2.103.1.1.5.1.15";
          config false;
        }
        leaf tfAlarmOperatorNote {
          type TAILF-ALARM-TC-MIB:TfUtf8String;
          tailf:snmp-oid "1.3.6.1.4.1.24961.2.103.1.1.5.1.16";
          config false;
        }
      }
    }
  }
}
