/*
 * Generated by confdc --mib2yang
 * Source: TAILF-ALARM-TC-MIB.mib
 */
module TAILF-ALARM-TC-MIB {
  namespace "http://tail-f.com/ns/mibs/TAILF-ALARM-TC-MIB/201208300000Z";
  prefix TAILF_ALARM_TC_MIB;
  tailf:id "";
  tailf:snmp-mib-module-name "TAILF-ALARM-TC-MIB";
  import tailf-common {
    prefix tailf;
  }

  revision 2012-08-30 {
    description
      "";
  }

  typedef TfAlarmIndex {
    type uint32 {
      range "0 .. 4294967295";
    }
  }

  typedef TfYANGResource {
    type string {
      length "min .. 255";
    }
  }

  typedef TfAlarmOperatorState {
    type enumeration {
      enum "none" {
        value 1;
      }
      enum "ack" {
        value 2;
      }
      enum "investigation" {
        value 3;
      }
      enum "observation" {
        value 4;
      }
      enum "closed" {
        value 5;
      }
      enum "other" {
        value 6;
      }
    }
  }

  typedef TfUtf8String {
    type string {
      length "min .. 255";
    }
  }

  typedef TfProbableCause {
    type uint32 {
      range "0 .. 4294967295";
    }
  }
}
