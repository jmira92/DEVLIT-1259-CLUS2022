/*
 * Generated by confdc --mib2yang
 * Source: TAILF-TOP-MIB.mib
 */
module TAILF-TOP-MIB {
  namespace "http://tail-f.com/ns/mibs/TAILF-TOP-MIB/201103010000Z";
  prefix TAILF_TOP_MIB;
  tailf:id "";
  tailf:snmp-mib-module-name "TAILF-TOP-MIB";
  import tailf-common {
    prefix tailf;
  }

  revision 2011-03-01 {
    description
      "";
  }
}
