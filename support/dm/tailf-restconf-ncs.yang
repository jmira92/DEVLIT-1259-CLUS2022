module tailf-restconf-ncs {
  namespace "http://tail-f.com/ns/restconf/ncs";
  prefix ncsrc;

  import tailf-restconf {
    prefix tfrcr;
  }
  import tailf-ncs {
    prefix ncs;
  }
  import tailf-common {
    prefix tailf;
  }

  organization "Tail-f Systems";

  description
    "This module defines extensions to RESTCONF for NCS.

     Copyright 2020 Cisco Systems, Inc.
     All rights reserved.
     Permission is hereby granted to redistribute this file without
     modification.";

  revision 2020-06-25 {
    description
      "Initial revision, released as part of NCS-5.4.";
  }

  augment "/tfrcr:result" {
    uses ncs:ncs-commit-result;
  }
}
