module tailf-ncs-cli-ned-notification {
  // Generated by yanger -t ncs
  tailf:mount-id "tailf-ncs-ned:cli-ned-notification-id";
  tailf:ncs-device-type "cli-ned";

  namespace "http://tail-f.com/ns/ncs-ned/notification/1.0";
  prefix cnn;
  // NCS drop tailf:id

  import ietf-yang-types {
    prefix yang;
  }
  import tailf-common {
    prefix tailf;
  }
  import tailf-ncs {
    prefix ncs;
  }

  augment "/ncs:devices/ncs:device/ncs:live-status" {
    container internal {
      tailf:ncs-device-type "cli-ned";
      tailf:display-when "not(../../ncs:capability) or ../../ncs:capability[ncs:uri='http://tail-f.com/ns/ncs-ned/notification/1.0']";
      // NCS drop tailf:callpoint
      container streams {
        list stream {
          key "name";
          leaf name {
            type string;
          }
          leaf description {
            type string;
            // NCS drop mandatory statement
          }
          leaf replaySupport {
            type boolean;
            // NCS drop mandatory statement
          }
          leaf replayLogCreationTime {
            type yang:date-and-time;
            // NCS drop mandatory statement
          }
          leaf replayLogAgedTime {
            type yang:date-and-time;
          }
        }
      }
    }
  }
}
