module tailf-ncs-rfc5277-device {
  // Generated by yanger -t ncs
  tailf:mount-id "tailf-ncs-ned:rfc5277-id";
  tailf:ncs-device-type "netconf";

  namespace "urn:ietf:params:xml:ns:netmod:notification";
  prefix nm;
  // NCS drop tailf:id

  import ietf-yang-types {
    prefix yang;
  }
  import tailf-common {
    prefix tailf;
  }
  import tailf-ncs {
    prefix ncs;
  }

  augment "/ncs:devices/ncs:device/ncs:live-status" {
    container netconf {
      tailf:ncs-device-type "netconf";
      tailf:display-when "not(../../ncs:capability) or ../../ncs:capability[ncs:uri='urn:ietf:params:netconf:capability:notification:1.0']";
      // NCS drop tailf:callpoint
      container streams {
        list stream {
          key "name";
          leaf name {
            type string;
          }
          leaf description {
            type string;
            // NCS drop mandatory statement
          }
          leaf replaySupport {
            type boolean;
            // NCS drop mandatory statement
          }
          leaf replayLogCreationTime {
            type yang:date-and-time;
            // NCS drop mandatory statement
          }
          leaf replayLogAgedTime {
            type yang:date-and-time;
          }
        }
      }
    }
  }
}
